# -*- coding: utf-8 -*-
"""
SMBS_AnimationPlayer.FCMacro - FreeCAD macro: bend sequence animation player
(Req 2 Phase F.2).

Install:
  1. Copy to FreeCAD macros directory (Macro -> Macros... -> Add).
  2. Edit SMBS_REPO_PATH below.
  3. Macro -> Macros... -> SMBS_AnimationPlayer -> Execute.

Usage:
  1. Execute macro.
  2. Select SMBS run directory (must contain 04/07/geometry.brep).
  3. Timeline dialog opens with Play/Pause/Step buttons + slider.
  4. Shape updates in active document per frame.

Honest marking:
  - Badge: VERIFIED (green) / FAILED (orange) / UNVERIFIED (gray)
  - Precision: VALID_PER_PANEL (green) / PREVIEW_ONLY (yellow)
  - Warning text shown below badges if not None

F.3 (future): tooling visualization (punch/die/frame).
"""

# ==== USER CONFIG ====
SMBS_REPO_PATH = r"/Users/badmc/Desktop/SMBS_BendSeq"
TICK_INTERVAL_MS = 500   # 2 fps default; edit for slower/faster playback
# =====================

import sys
from pathlib import Path

import FreeCAD as App
import FreeCADGui as Gui
import Part
from PySide6 import QtCore, QtWidgets


OBJECT_NAME = "SMBS_Animation"


def _to_fc_shape(shape):
    """Convert OCC TopoDS_Shape to FreeCAD Part.Shape via Part.__fromPythonOCC__."""
    if shape is None:
        return None
    if isinstance(shape, Part.Shape):
        return shape
    if hasattr(Part, "__fromPythonOCC__"):
        try:
            return Part.__fromPythonOCC__(shape)
        except Exception:
            pass
    try:
        return Part.Shape(shape)
    except Exception:
        return None


def _update_feature(doc, name, fc_shape):
    """In-place update of Part::Feature: set .Shape, recompute. Removes
    object if fc_shape is None (e.g. tooling not loaded)."""
    if fc_shape is None:
        obj = doc.getObject(name)
        if obj is not None:
            doc.removeObject(name)
            doc.recompute()
            Gui.updateGui()
        return None
    obj = doc.getObject(name)
    if obj is None:
        obj = doc.addObject("Part::Feature", name)
    obj.touch()
    obj.Shape = fc_shape
    obj.Visibility = True
    doc.recompute()
    Gui.updateGui()
    return obj


class AnimationPlayerDialog(QtWidgets.QDialog):
    def __init__(self, parent=None):
        super().__init__(parent)
        self.setWindowTitle("SMBS Animation Player")
        self.resize(560, 260)

        self.controller = None
        self._first_show = True
        self.machine = None      # PressBrakeMachine
        self.assembly = None     # ToolingAssembly
        self.punch_shape = None  # Part.Shape or None
        self.die_shape = None    # Part.Shape or None
        self.machine_frame_shape = None  # Part.Shape or None (None в F.3a)
        self._init_ui()
        self._load_run()

    def _init_ui(self):
        layout = QtWidgets.QVBoxLayout(self)

        self.lbl_header = QtWidgets.QLabel("—")
        font = self.lbl_header.font()
        font.setBold(True)
        font.setPointSize(font.pointSize() + 2)
        self.lbl_header.setFont(font)
        layout.addWidget(self.lbl_header)

        badges = QtWidgets.QHBoxLayout()
        self.lbl_verif = QtWidgets.QLabel("—")
        self.lbl_precision = QtWidgets.QLabel("—")
        for lbl in (self.lbl_verif, self.lbl_precision):
            lbl.setAlignment(QtCore.Qt.AlignCenter)
            lbl.setMinimumHeight(28)
            lbl.setStyleSheet("border-radius: 4px; padding: 2px 8px; color: white;")
        badges.addWidget(self.lbl_verif)
        badges.addWidget(self.lbl_precision)
        layout.addLayout(badges)

        self.lbl_warning = QtWidgets.QLabel("")
        self.lbl_warning.setWordWrap(True)
        self.lbl_warning.setStyleSheet("color: #616161; font-style: italic;")
        layout.addWidget(self.lbl_warning)

        tooling_row = QtWidgets.QHBoxLayout()
        self.lbl_tooling = QtWidgets.QLabel("—")
        self.lbl_machine_frame = QtWidgets.QLabel("—")
        for lbl in (self.lbl_tooling, self.lbl_machine_frame):
            lbl.setAlignment(QtCore.Qt.AlignCenter)
            lbl.setMinimumHeight(28)
            lbl.setStyleSheet("border-radius: 4px; padding: 2px 8px; color: white; background-color: rgb(127,127,127);")
        tooling_row.addWidget(self.lbl_tooling)
        tooling_row.addWidget(self.lbl_machine_frame)
        layout.addLayout(tooling_row)

        self.slider = QtWidgets.QSlider(QtCore.Qt.Horizontal)
        self.slider.setMinimum(0)
        self.slider.valueChanged.connect(self._on_slider_changed)
        layout.addWidget(self.slider)

        controls = QtWidgets.QHBoxLayout()
        self.btn_reset = QtWidgets.QPushButton("Reset")
        self.btn_back = QtWidgets.QPushButton("◀ Step")
        self.btn_play = QtWidgets.QPushButton("▶ Play")
        self.btn_fwd = QtWidgets.QPushButton("Step ▶")
        self.btn_reset.clicked.connect(self._on_reset)
        self.btn_back.clicked.connect(self._on_step_back)
        self.btn_play.clicked.connect(self._on_play_pause)
        self.btn_fwd.clicked.connect(self._on_step_fwd)
        controls.addWidget(self.btn_reset)
        controls.addWidget(self.btn_back)
        controls.addWidget(self.btn_play)
        controls.addWidget(self.btn_fwd)
        layout.addLayout(controls)

        self.lbl_status = QtWidgets.QLabel("")
        self.lbl_status.setStyleSheet("color: #616161;")
        layout.addWidget(self.lbl_status)

        self.timer = QtCore.QTimer(self)
        self.timer.setInterval(TICK_INTERVAL_MS)
        self.timer.timeout.connect(self._on_tick)

    def _load_run(self):
        from smbs_core.viewer.run_loader import load_run, RunLoaderError
        from smbs_core.viewer.graph_builder import build_graphs, GraphBuilderError
        from smbs_core.viewer.player import Player
        from smbs_core.viewer.fc_animation import AnimationController

        repo = Path(SMBS_REPO_PATH)
        if not repo.is_dir():
            QtWidgets.QMessageBox.critical(self, "SMBS", f"SMBS_REPO_PATH invalid: {SMBS_REPO_PATH}")
            self.close()
            return
        if str(repo) not in sys.path:
            sys.path.insert(0, str(repo))

        run_dir_str = QtWidgets.QFileDialog.getExistingDirectory(
            self, "Select SMBS run directory", str(repo / "runs")
        )
        if not run_dir_str:
            self.close()
            return

        try:
            artifacts = load_run(Path(run_dir_str))
            graphs = build_graphs(artifacts)
        except (RunLoaderError, GraphBuilderError) as e:
            QtWidgets.QMessageBox.critical(self, "SMBS", f"Failed to load run: {e}")
            self.close()
            return

        try:
            from smbs_core.geometry_backend.backends.pythonocc_backend import PythonOCCBackend
            backend = PythonOCCBackend()
            player = Player(artifacts, graphs, backend)
            _ = player.frames   # eagerly build; raises PlayerError on bad 09
        except Exception as e:
            QtWidgets.QMessageBox.critical(self, "SMBS", f"Failed to build player: {e}")
            self.close()
            return

        self.controller = AnimationController(player)
        try:
            from smbs_core.models.tooling import ToolingKind
            from smbs_core.Physics.machine_kinematics import PressBrakeMachine
            self.machine = PressBrakeMachine.with_default_tooling()
            self.assembly = self.machine.setup_assembly(backend)
            self.punch_shape = self.assembly.get_world_shape(ToolingKind.PUNCH)
            self.die_shape = self.assembly.get_world_shape(ToolingKind.DIE)
            self.machine_frame_shape = self.assembly.get_world_shape(ToolingKind.MACHINE_FRAME)
        except Exception as e:
            self.lbl_status.setText(f"Tooling assembly failed: {e}")
            self.machine = None
            self.assembly = None
        self.slider.setMaximum(player.total - 1)
        self.controller.reset()
        self._update_ui()
        self.lbl_status.setText(f"Loaded {run_dir_str} — {player.total} frames")
        self._render_current()

    def _ensure_document(self):
        if App.ActiveDocument is None:
            App.newDocument("SMBS_Animation")
            try:
                Gui.ActiveDocument = Gui.activeDocument()
            except Exception:
                pass
        return App.ActiveDocument

    def _render_current(self):
        frame = self.controller.current()
        if frame is None:
            return
        doc = self._ensure_document()
        fc_part = _to_fc_shape(frame.step_view.state.shape)
        _update_feature(doc, OBJECT_NAME, fc_part)
        fc_punch = _to_fc_shape(self.punch_shape) if self.punch_shape is not None else None
        _update_feature(doc, "SMBS_Punch", fc_punch)
        fc_die = _to_fc_shape(self.die_shape) if self.die_shape is not None else None
        _update_feature(doc, "SMBS_Die", fc_die)
        fc_frame = _to_fc_shape(self.machine_frame_shape) if self.machine_frame_shape is not None else None
        _update_feature(doc, "SMBS_MachineFrame", fc_frame)
        if self._first_show:
            try:
                Gui.SendMsgToActiveView("ViewFit")
            except Exception:
                pass
            self._first_show = False

    def _update_ui(self):
        from smbs_core.viewer.fc_animation import (
            format_verification_badge, format_precision_badge, format_step_header,
        )
        frame = self.controller.current()
        if frame is None:
            return
        self.lbl_header.setText(format_step_header(frame))
        vt, vc = format_verification_badge(frame)
        pt, pc = format_precision_badge(frame)
        self.lbl_verif.setText(vt)
        self.lbl_verif.setStyleSheet(
            f"background-color: rgb({int(vc[0]*255)},{int(vc[1]*255)},{int(vc[2]*255)}); "
            f"border-radius: 4px; padding: 2px 8px; color: white;"
        )
        self.lbl_precision.setText(pt)
        self.lbl_precision.setStyleSheet(
            f"background-color: rgb({int(pc[0]*255)},{int(pc[1]*255)},{int(pc[2]*255)}); "
            f"border-radius: 4px; padding: 2px 8px; color: white;"
        )
        self.lbl_warning.setText(frame.step_view.geometry_warning or "")
        from smbs_core.viewer.fc_animation import (
            format_machine_frame_badge, format_tooling_badge,
        )
        mt, mc = format_machine_frame_badge(self.machine_frame_shape is not None)
        tt, tc = format_tooling_badge(self.punch_shape is not None, self.die_shape is not None)
        self.lbl_machine_frame.setText(mt)
        self.lbl_machine_frame.setStyleSheet(
            f"background-color: rgb({int(mc[0]*255)},{int(mc[1]*255)},{int(mc[2]*255)}); "
            f"border-radius: 4px; padding: 2px 8px; color: white;"
        )
        self.lbl_tooling.setText(tt)
        self.lbl_tooling.setStyleSheet(
            f"background-color: rgb({int(tc[0]*255)},{int(tc[1]*255)},{int(tc[2]*255)}); "
            f"border-radius: 4px; padding: 2px 8px; color: white;"
        )
        self.slider.blockSignals(True)
        self.slider.setValue(frame.frame_index)
        self.slider.blockSignals(False)
        self.btn_play.setText("❚❚ Pause" if self.controller.is_playing() else "▶ Play")

    def _on_reset(self):
        self.timer.stop()
        self.controller.reset()
        self._update_ui()
        self._render_current()

    def _on_play_pause(self):
        self.controller.toggle()
        if self.controller.is_playing():
            self.timer.start()
        else:
            self.timer.stop()
        self._update_ui()
        self._render_current()

    def _on_step_fwd(self):
        self.timer.stop()
        self.controller.step_forward()
        self._update_ui()
        self._render_current()

    def _on_step_back(self):
        self.timer.stop()
        self.controller.step_backward()
        self._update_ui()
        self._render_current()

    def _on_slider_changed(self, value: int):
        self.timer.stop()
        self.controller.pause()
        # Seek: reset then advance to value
        self.controller.player.reset()
        for _ in range(value):
            if self.controller.player.next() is None:
                break
        self._update_ui()
        self._render_current()

    def _on_tick(self):
        result = self.controller.tick()
        if result is None or not self.controller.is_playing():
            self.timer.stop()
        self._update_ui()
        self._render_current()

    def closeEvent(self, event):
        self.timer.stop()
        doc = App.ActiveDocument
        if doc is not None:
            for name in (OBJECT_NAME, "SMBS_Punch", "SMBS_Die", "SMBS_MachineFrame"):
                obj = doc.getObject(name)
                if obj is not None:
                    doc.removeObject(name)
        super().closeEvent(event)


def run_macro() -> None:
    try:
        Gui.runCommand('Std_ViewReportView', 0)
    except Exception:
        pass

    repo = Path(SMBS_REPO_PATH)
    if not repo.is_dir():
        QtWidgets.QMessageBox.critical(None, "SMBS", f"Invalid repo path: {SMBS_REPO_PATH}")
        return
    if str(repo) not in sys.path:
        sys.path.insert(0, str(repo))

    dialog = AnimationPlayerDialog()
    dialog.exec()


if __name__ == "__main__":
    run_macro()
